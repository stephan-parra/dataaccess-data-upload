FME workspace DataAccess-Data-Batch-Loader.fmw

Readers:
- CSV2_1: CSV2 from D:\DATA\DataAccess-Batch-Tests\SOURCEDATA\DataAccess-Batch-Product-Upload-test1.csv in LL-WGS84
- JSON_1: JSON from D:\DATA\DataAccess-Batch-Tests\SOURCEDATA\json-payload-template.json

Writers:
- TEXTLINE_1: TEXTLINE to D:\DATA\DataAccess-Batch-Tests\TRANSLATED

Note: Leave this disabled, / DO NOT REMOVE
JSONFeature (reader JSON_1) [off]
    attributes: json_DataOwnerId string, json_FileName string, json_PreviewFile string, json_FileSize string, json_IsMultiPartUpload string, json_ProductName string, json_ShortDescription string, json_LongDescription string, json_DateDataCaptured string, json_DateDataExpired string, json_DataFormatType string, json_Tags{} string, json_DataResellPrice string, json_DataGeoShape string
    -> AttributeManager
CSV (reader CSV2_1)
    attributes: FileName varchar(24), FileFormat varchar(3), TypeOfData varchar(3), ProductName varchar(7), ShortDescription varchar(28), LongDescription varchar(381), CapturedDate datetime, ExpiryDate datetime, Price uint32, Tags varchar(15), DataOwnerID varchar(36), FileSize uint32, WKT varchar(2452)
    -> DateTimeConverter
DateTimeConverter
    DATETIME_ATTR = CapturedDate ExpiryDate
    OUT_FORMAT = ISO
    PASSTHROUGH = NO
    REPAIR_INPUT = YES
    -> AttributeManager
AttributeManager
    ATTR_TABLE:
      SET_TO json_DataOwnerId (buffer) = @Value(DataOwnerID)
      SET_TO json_FileName (buffer) = @Value(FileName)
      SET_TO json_FileSize (buffer) = @Value(FileSize)
      SET_TO json_IsMultiPartUpload (buffer) = false
      SET_TO json_ProductName (buffer) = @Value(ProductName)
      SET_TO json_ShortDescription (buffer) = @Value(ShortDescription)
      SET_TO json_LongDescription (buffer) = @Value(LongDescription)
      SET_TO json_DateDataCaptured (datetime) = @Value(CapturedDate)
      SET_TO json_DateDataExpired (datetime) = @Value(ExpiryDate)
      SET_TO json_DataFormatType (buffer) = @Value(TypeOfData)
      SET_TO Tags (varchar(15)) = @Value(Tags)
      SET_TO json_DataResellPrice (buffer) = @Value(Price)
      SET_TO json_DataGeoShape (buffer) = @Value(WKT)
      REMOVE json_Tags{} (buffer)
      REMOVE FileName (varchar(24))
      REMOVE FileFormat (varchar(3))
      REMOVE TypeOfData (varchar(3))
      REMOVE ProductName (varchar(7))
      REMOVE ShortDescription (varchar(28))
      REMOVE LongDescription (varchar(381))
      REMOVE CapturedDate (buffer)
      REMOVE ExpiryDate (buffer)
      REMOVE Price (uint32)
      REMOVE DataOwnerID (varchar(36))
      REMOVE FileSize (uint32)
      REMOVE WKT (varchar(2452))
    -> AttributeEscaper
AttributeEscaper
    CASE = NO
    escapeBackslash = Yes
    escapeValues = "
    escapedString = @Value(json_LongDescription)
    -> BulkAttributeRenamer
BulkAttributeRenamer
    ATTRCHOICE_ACTION = SELECTED
    ATTRLIST = json_DataFormatType json_DataGeoShape json_DataOwnerId json_DataResellPrice json_DateDataCaptured json_DateDataExpired json_FileName json_FileSize json_IsMultiPartUpload json_LongDescription json_PreviewFile json_ProductName json_ShortDescription Tags
    CASE_DISP = YES
    MODE_CHOICE = RENAME
    PATTERN_ACTION_DISP = REMOVEPREFIX
    REPLACE_STR = json_
    ATTRCHOICE = Selected Attributes
    -> StringConcatenator
StringConcatenator
    ACTION = Create New Attribute
    PARM_LINE:
      {
      "DataOwnerId": "@Value(DataOwnerId)",
      "FileName": "@Value(FileName)",
      "PreviewFile": "@Value(PreviewFile)",
      "FileSize": @Value(FileSize),
      "IsMultiPartUpload": @Value(IsMultiPartUpload),
      "ProductName": "@Value(ProductName)",
      "ShortDescription": "@Value(ShortDescription)",
      "LongDescription": "@Value(_escapedString)",
      "DateDataCaptured": "@Value(DateDataCaptured)",
      "DateDataExpired": "@Value(DateDataExpired)",
      "DataFormatType": "@Value(DataFormatType)",
      "Tags": @Value(Tags),
      "DataResellPrice": @Value(DataResellPrice),
      "DataGeoShape": "@Value(DataGeoShape)"
      }
    VAL_ATTR = json-payload
    -> text_line (writer TEXTLINE_1)
    -> TestFilter
text_line (writer TEXTLINE_1) [off]
    attributes: text_line_data buffer
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(DataGeoShape) CONTAINS POLYGON",Polygons,"BOOL_OP,OR,COMPOSITE_TEST,""""""1"""""",TEST_CLAUSE,CASE_INSENSITIVE_TEST @Value(DataGeoShape) CONTAINS LINESTRING",Polylines,"BOOL_OP,OR,COMPOSITE_TEST,""""""1"""""",TEST_CLAUSE,CASE_INSENSITIVE_TEST @Value(DataGeoShape) CONTAINS POINT",Points
    Polygons -> API-Get-s3-Signed-URL
    Polylines -> GeometryReplacer
GeometryReplacer
    KIND = wkt
    OGC_WKT_PRECISION = FLOAT_64
    REMOVE_ATTRIBUTE = Yes
    SOURCE = @Value(DataGeoShape)
    KIND_LONG = OGC Well Known Text
    OGC_WKT_PRECISION_DISPLAY = 64-bit
    -> Bufferer
Bufferer
    ANGLE = 22.5
    CAP_STYLE_LOOKUP = CAP_ARC
    CORNER_STYLE_LOOKUP = JOIN_ARC
    MODE = AREA
    OFFSET = 1
    OFFSET_UNITS = METERS
    PRECISION = APPROX
    CAP_STYLE = Arc
    CORNER_STYLE = Arc
    BUFFERED -> GeometryExtractor
GeometryExtractor
    ATTR = DataGeoShape
    KIND = wkt
    OGCVERSION = 1.2
    OGC_WKT_PRECISION = FLOAT_64
    REMOVE_GEOMETRY = Yes
    KIND_LONG = OGC Well Known Text
    OGC_WKT_PRECISION_DISPLAY = 64-bit
    -> StringConcatenator_2
StringConcatenator_2
    ACTION = Overwrite Existing Attributes
    ATTRLIST = json-payload
    PARM_LINE:
      fme_basicstring:18%19%16%16%19%19%15%16%23%25%18%19%24%24%23%22%24%24%23%23%22%22%11%12%21%23%19%20%3:{
      "DataOwnerId": "@Value(DataOwnerId)",
      "FileName": "@Value(FileName)",
      "PreviewFile": "@Value(PreviewFile)",
      "FileSize": @Value(FileSize),
      "IsMultiPartUpload": @Value(IsMultiPartUpload),
      "ProductName": "@Value(ProductName)",
      "ShortDescription": "@Value(ShortDescription)",
      "LongDescription": "@Value(_escapedString)",
      "DateDataCaptured": "@Value(DateDataCaptured)",
      "DateDataExpired": "@Value(DateDataExpired)",
      "DataFormatType": "@Value(DataFormatType)",
      "Tags": @Value(Tags),
      "DataResellPrice": @Value(DataResellPrice),
      "DataGeoShape": "@Value(DataGeoShape)"
      }
    -> API-Get-s3-Signed-URL
API-Get-s3-Signed-URL: HTTPCaller
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://mifctbkjnf.execute-api.ap-southeast-2.amazonaws.com/v1/dataaccess/upload
    TRANSFER_TIMEOUT_LENGTH = 90
    UPLOAD_BODY = @Value(json-payload)
    UPLOAD_TYPE = STRING_UPLOAD
    USE_COOKIES = No
    VERIFY_SSL_CERTIFICATES = Yes
    UPLOAD_CONTENT_TYPE = JSON (application/json)
    -> JSONExtractor
    <REJECTED> -> Upload_API__Rejected_
JSONExtractor
    EXTRACT_QUERY_TABLE = uploadUrl json["presignedUrl"]
    JSON_DOCUMENT = @Value(_response_body)
    READ_FROM_FILE = NO
    EVALUATED -> JSONExtractor_Evaluated
    EVALUATED -> API-Upload-to-S3
JSONExtractor_Evaluated: Inspector
API-Upload-to-S3: HTTPCaller
    CLIENT_CERTIFICATE_TYPE = NONE
    CONNECTION_TIMEOUT_LENGTH = 60
    CONTENT_TYPE_LOOKUP = application/zip
    ERROR_ATTR = _error
    FOLLOW_REDIRECTS = FOLLOW_WITH_GET
    HTTP_METHOD = PUT
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _upload_response_body
    TARGET_ATTR_ENCODING = auto-detect
    TARGET_URL = @Value(uploadUrl)
    TRANSFER_TIMEOUT_LENGTH = 90
    UPLOAD_FILE = D:\DATA\DataAccess-Batch-Tests\SOURCEDATA\@Value(FileName)
    UPLOAD_TYPE = FILE_UPLOAD
    USE_COOKIES = No
    VERIFY_SSL_CERTIFICATES = Yes
    UPLOAD_CONTENT_TYPE = application/zip
    -> HTTPCaller_Output
    <REJECTED> -> HTTPCaller__Rejected_
HTTPCaller_Output: Logger
    LOG_FEATURE = LOG_ONLY
    MAXCOORDS = 20
    MAXFEATS = 20
    MESSAGE = Feature is:
    SEVERITY = INFO
HTTPCaller__Rejected_: Inspector
Upload_API__Rejected_: Logger
    LOG_FEATURE = LOG_ONLY
    MAXCOORDS = 20
    MAXFEATS = 20
    MESSAGE = Feature is:
    SEVERITY = INFO

FME custom transformer AttributeEscaper
Use the AttributeEscaper to specify one or more characters to escape with a backslash \ character in a specified string or attribute. For example, "\\internal.server\file.ext" can be transformed to "\\\\internal.server\\file.ext" if the \ character is specified in parameters.
This transformer is designed to be similar in functionality compared to using multiple StringReplacer transformers or using Regex within one StringReplacer. Please note that performance is likely better using a single StringReplacer, this transformer cannot escape commas by design, and it has not been tested against i18n or l10n characters.
Input Ports
Input
This transformer accepts any features. Features should have a string of characters to operate on in at least one specified attribute.  
Parameters
String to Escape: Specify a string or attribute containing a string that has characters to escape.
Escape Backslash: Specify whether to escape the \ backslash character.
Case Senstive: Specify whether the replacement is case-sensitve. If 'No', then case will be converted to how the character is specified in 'Characters to Escape'.
Characters to Escape: Specify one or more characters to escape with a \ blackslash character. Characters must be separated by , comma characters. Do not specify \ backslash here or there may be unexpected results.  
Output Ports
Output
Features are output with an additional attribute, _escapedString, that has the modified or transformed string.

Parameters:
- escapedString =   # String to Escape
- escapeBackslash = Yes   # Escape Backslash \
- CASE = NO   # Case Sensitive
- escapeValues =   # Characters to Escape (Comma Separated)

Input (input)
    -> ParameterFetcher
ParameterFetcher
    ATTR_LIST = _escapeValues $(escapeValues)
    -> VariableRetriever_2
Input (output)
Note: Cleanup Attributes
AttributeManager
    ATTR_TABLE:
      REMOVE _replaceList{}
      REMOVE _element_count
      REMOVE _count
      REMOVE _escapeValues
      REMOVE _looped
    -> Output (output)
Output (output)

Bookmark: Check if Variable Has a Value (Determine if First Iteration)
Note: Set Value if Not
VariableRetriever_2
    SCOPE = Global
    VALUE_ATTR = _escapedString
    VARNAME = _path_var
    -> TestFilter_2
TestFilter_2
    DEFAULT_VALUE = VariableSet
    TEST_LIST = BOOL_OP,OR,COMPOSITE_TEST,<Unused>,TEST_CLAUSE,"TEST @Value(_escapedString) NOT_ATTRIBUTE_HAS_VALUE """"",VariableUnset
    VariableUnset -> ParameterFetcher_2
    VariableSet -> ParameterFetcher_3
ParameterFetcher_2
    ATTR_LIST = _escapedString $(escapedString)
    -> TestFilter_4
ParameterFetcher_3: Junction
    -> AttributeSplitter

Bookmark: Handle Backslash \
TestFilter_4
    DEFAULT_VALUE = EscapeBackslash
    TEST_LIST = BOOL_OP,OR,COMPOSITE_TEST,<Unused>,TEST_CLAUSE,"TEST $(escapeBackslash) = No",NoBackslash
    NoBackslash -> ParameterFetcher_3
    EscapeBackslash -> StringReplacer_2
StringReplacer_2
    CASE = NO
    FIND_TEXT = \
    NO_MATCH = _FME_NO_OP_
    REGEXP = NO
    REPLACE_TEXT = \\
    SRC_ATTRS = _escapedString
    -> ParameterFetcher_3

Bookmark: Parse Values to Escape
AttributeSplitter
    ATTR_NAME = _escapeValues
    DELIMITER = ,
    DROP_EMPTY_PARTS = No
    LIST_NAME = _replaceList
    TRIM_COMMAND = trim
    TRIM_OPTION = Both
    -> ListElementCounter
ListElementCounter
    CNT_ATTR = _element_count
    LIST_NAME = _replaceList{}
    -> Counter
Counter
    CNT_ATTR = _count
    DOMAIN = counter
    SCOPE = Global
    START = 0
    SCOPEVAR = Global
    -> StringReplacer
StringReplacer
    CASE = $(CASE)
    FIND_TEXT = @Value(_replaceList{@Value(_count)})
    NO_MATCH = _FME_NO_OP_
    REGEXP = NO
    REPLACE_TEXT = \@Value(_replaceList{@Value(_count)})
    SRC_ATTRS = _escapedString
    -> VariableSetter
VariableSetter
    SCOPE = Global
    VALUE = @Value(_escapedString)
    VARNAME = _path_var
    -> AttributeManager_2

Bookmark: Loop Logic, Increase Counter
AttributeManager_2
    ATTR_TABLE:
      REMOVE _path
      REMOVE _attr
      SET_TO _count = @Evaluate(@Value(_count)+1)
      SET_TO _looped
    -> TestFilter
TestFilter
    DEFAULT_VALUE = NoLoop
    TEST_LIST = BOOL_OP,OR,COMPOSITE_TEST,<Unused>,TEST_CLAUSE,"TEST @Value(_count) < @Value(_element_count)",Loop
    Loop -> Input (output)
    NoLoop -> AttributeManager
